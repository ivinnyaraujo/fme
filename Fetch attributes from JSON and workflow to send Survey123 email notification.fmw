FME workspace Fetch attributes from JSON and workflow to send Survey123 email notification.fmw
Title: Survey123 Email Notification (FME Flow Automations)
Description: Goal: Send an email notification to users following the submission of a Survey123 inspection, indicating that further action is required.
This workspace extracts attribute values from a JSON file, which is generated whenever a new Survey123 is submitted. To accomplish the email notification, the workspace needs to be published on FME Flow with the appropriate automation parameters configured.
History: 19-10-2023,Ivy A,Training - Survey123 Email Notification

Parameters:
- webhook.feature = {   "attributes": {     "installation_complete": "No",     "followup_action_required": "Yes",     "follow_up_action_comment": "Test"   },   "layerInfo": {     "name": "survey",     "id": 0   } }   # Webhook Feature

Writers:
- AUTOMATIONS_1: AUTOMATIONS

Note: READ ME / Goal: Send an email notification to users following the submission of a Survey123 inspection, indicating that further action is required. / This workspace extracts attribute values from a JSON file, which is generated whenever a new Survey123 is submitted. To accomplish the email notification, the workspace needs to be published on FME Flow with the appropriate automation parameters configured.
Creator_2
    GEOMTYPE = Geometry Object
    NUM = 1
    CREATED -> ParameterFetcher_2
Note: In User Parameter default value, add a submitted log from FME Flow automation and call this value using parameter Fetcher. / In FME Flow, set up: Webhook > Output Keys > Webhook Keys / webhook.feature / webhook.eventType / webhook.applyEdits / To check JSON from survey123 Log, go to FME FLOW, > Automations > Menu > View Log File
ParameterFetcher_2
    ATTR_LIST = _webhook.feature $(webhook.feature)
    -> JSONExtractor_3
Note: Fragments JSON file to extract desired attribute values
JSONExtractor_3
    EXTRACT_QUERY_TABLE = installationcomplete json["attributes"]["installation_complete"] followup_action_required json["attributes"]["followup_action_required"] reason_followup_action json["attributes"]["follow_up_action_comment"]
    JSON_DOCUMENT = @Value(_webhook.feature)
    READ_FROM_FILE = NO
    EVALUATED -> Tester
Note: Check if further action is required after an survey123 inspection is submitted
Tester
    BOOL_OP = OR
    TEST_CLAUSE = CASE_INSENSITIVE_TEST @Value(followup_action_required) = Yes
    TEST_MODE = CASE_INSENSITIVE_TEST
    PASSED -> AttributeCreator
    FAILED -> FeatureHolder
Note: Create join attribute
AttributeCreator
    ATTR_TABLE = SET_TO join = 1
    -> FeatureJoiner [RIGHT]
    -> HTMLReportGenerator
Note: Create customised email
HTMLReportGenerator
    CONTENT_LIST = HTML
    PAGE_CONFIG:
      HTML{{HTML;<p>Hello,</p>
      <p><br></p>
      <p>This is to notify you that further action is required from Survey123 .</p>
      <p><br></p>
      <p>Reason for follow-up action: @Value(reason_followup_action)</p>
      <p><br></p>
      <p>This is a system-generated email, please don&apos;t reply.</p>;FME_CONTROLLER_QUERY_FILE;transformers/dependencies/html5/Custom HTML.fme;FME_CONTROLLER_CHOICE;Custom HTML}}
    -> AttributeCreator_2
Note: Create join attribute
AttributeCreator_2
    ATTR_TABLE = SET_TO join = 1
    -> FeatureJoiner [LEFT]
FeatureJoiner
    ATTR_CONFLICT_RES = Use Left
    GEOMETRY_HANDLING = Use Left
    JOIN_KEYS = join join AUTO
    JOIN_MODE = Inner
    JOINED -> AttributeKeeper
AttributeKeeper
    CREATE_BULK_MODE_FEATURES = NO
    KEEP_ATTRS = html_content
    -> action_email (writer AUTOMATIONS_1)
Note: nothing happens if actionrequired is no
FeatureHolder

Bookmark: Writer - Automation
Note: Writer: FME Flow Automations
action_email (writer AUTOMATIONS_1) [off]
    attributes: html_content string
