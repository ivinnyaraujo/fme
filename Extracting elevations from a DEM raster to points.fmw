FME workspace Extracting elevations from a DEM raster to points.fmw

Parameters:
- DestDataset_CSV2 =
- DestDataset_SHAPEFILE =
- SourceDataset_GEOTIFF =
- SourceDataset_SHAPEFILE =

Readers:
- SHAPEFILE_1: SHAPEFILE from $(SourceDataset_SHAPEFILE)
- GEOTIFF_1: GEOTIFF from $(SourceDataset_GEOTIFF)

Writers:
- CSV2_1: CSV2 to $(DestDataset_CSV2)
- SHAPEFILE_2: SHAPEFILE to $(DestDataset_SHAPEFILE)

Note: Extracting elevations data from a DEM raster to point shapefile (Christchurch Addresses) with FME
Elevation_Address_CHC (writer SHAPEFILE_2)
    attributes: Elevation_ varchar(200), full_addre varchar(19), full_road_ varchar(33), address_id long, change_id long, address_ty varchar(5), unit_value varchar(5), address_nu long, address__1 varchar(3), address__2 long, water_rout varchar(19), water_name varchar(35), suburb_loc varchar(40), town_city varchar(25), full_add_1 varchar(68), road_secti long, gd2000_xco double, gd2000_yco double, water_ro_1 varchar(19), water_na_1 varchar(35), suburb_l_1 varchar(40), town_city_ varchar(25), full_roa_1 varchar(33), full_add_2 varchar(68), _band___va double, _band___pa double

Bookmark: Input Data - NZGD2000
Note: Canterbury - Christchurch and Selwyn LiDAR 1m DEM (2015), 14 raster files
GEOTIFF (reader GEOTIFF_1)
    -> RasterMosaicker
Note: Christchurch addresses (from LINZ database) point .shp
nz-street-address (reader SHAPEFILE_1)
    attributes: address_id long, change_id long, address_ty varchar(5), unit_value varchar(5), address_nu long, address__1 varchar(3), address__2 long, water_rout varchar(19), water_name varchar(35), suburb_loc varchar(40), town_city varchar(25), full_addre varchar(19), full_road_ varchar(33), full_add_1 varchar(68), road_secti long, gd2000_xco double, gd2000_yco double, water_ro_1 varchar(19), water_na_1 varchar(35), suburb_l_1 varchar(40), town_city_ varchar(25), full_roa_1 varchar(33), full_add_2 varchar(68)
    -> PointOnRasterValueExtractor [POINT]

Bookmark: Merges multiple raster features into a single raster feature
RasterMosaicker
    ACCUM_ATTRS_NAME = Use Attributes From One Feature
    INTERPOLATION_TYPE_NAME = Nearest Neighbor
    MERGE_PALETTES_NAME = Yes
    OVERLAPPING_VALUES = average
    SNAPPING_TYPE_NAME = Resample
    -> PointOnRasterValueExtractor [RASTER]

Bookmark: Getting Elevation Data
Note: At each point’s position, values are interpolated for the corresponding point on the raster for each band and/or palette. A variety of interpolation methods are available. The interpolated values are added to a new list attribute, named _band{}.value and _band{}.palette{}.value
PointOnRasterValueExtractor
    INTERPOLATION_TYPE_NAME = Nearest Neighbor
    POINT -> AttributeRenamer
Note: Renames one or more attributes, retaining the attribute’s current values / Used to create Attribute "Elevation"
AttributeRenamer
    ATTR_TABLE = RENAME_SET_DEFAULT _band{0}.value > Elevation_meter
    MISSING_INPUT_ATTRS = REMOVE
    -> Elevation_Address_CHC (writer SHAPEFILE_2)
