FME workspace Join tabular and spatial data with User Parameters to Publish on FME Server.fmwt
Title: Join tabular and spatial data with User Parameters to Publish on FME Server
Description: Join tabular and spatial data with User Parameters to Publish on FME Server
History: February 2023,Ivinny Araujo,Initial Release (developed with FME Desktop 2022.1.1.0)

Parameters:
- INPUT_DATA =   # Input Data
- INPUT_XLSX =   # Upload Asset List
- INPUT_ArcGIS_REST_SERVICE =   # Insert ArcGIS REST Service URL
- ArcGIS_REST_SERVICE_FEATURETYPES_TO_READ =
- JOIN_ASSET_LIST_GIS =   # Match Asset List to the GIS
- ASSET_LIST_ATTRIBUTE_TO_JOIN = ASSETID   # "" Select asset list attribute name to join to the GIS
- GIS_ATTRIBUTE_TO_JOIN =   # Type GIS attribute name to join to asset list
- GEOSPATIAL_OUTPUT =   # Geospatial Output Format
- DESTINATION_FOLDER =   # Select destination folder
- OUTPUT_FORMAT = SHAPEFILE
- OUTPUT_COORDINATE_SYSTEM = EPSG:2193
- FTP_FEATURE_TYPE_NAME_EXP = GeospatialOutput   # Type Feature Type Name

Readers:
- XLSXR_2: XLSXR from $(INPUT_XLSX)

Writers:
- GENERIC_1: GENERIC to $(DESTINATION_FOLDER) in $(OUTPUT_COORDINATE_SYSTEM)

Note: READ ME / When managing assets, it is common to have an list of assets that need to be mapped to be serviced. This workspace contains user parameters and uses feature reader, allowing users to input an asset list (excel) and have these assets in a geospatial format (ready to be mapped). / - FeatureReader transformer allow users to input Esri ArcGIS Server Feature Service (usually available in open data websites) URL. To expose the desired attributes, please, specify the attribute names in the Attribute Exposer transformer. / - To join the tabular data to the geospatial data, it was used Feature Joiner Transformer. Users need to specify the common attributes that will mach these 2 datasets. / - The output can be a .shp or .gdb file and the user can choose the desired output coordinate system / - With some minor changes, this workflow can be used on FME Server. It will allow the development of an Workspace App that can be used by non FME users in a wide team. / _____________________________________________________________________________________________ / Instead of download the geospatial output in your local, you can make it available in your ArcGIS Enterprise Portal using the Writer Esri ArcGIS Portal Feature Service, allowing non GIS users to verify the location of the assets they want to target.
Note: Specify attributes to expose
AttributeExposer_3
    ATTR_LIST = Name
    -> FeatureJoiner [RIGHT]
Note: Get geolocation for all assets in the uploaded list
FeatureJoiner
    ATTR_CONFLICT_RES = Prefer Left
    GEOMETRY_HANDLING = Prefer Right
    JOIN_KEYS = $(ASSET_LIST_ATTRIBUTE_TO_JOIN) $(GIS_ATTRIBUTE_TO_JOIN) AUTO
    JOIN_MODE = Inner
    JOINED -> AttributeRemover
    <REJECTED> -> Junction
AttributeRemover
    REMOVE_ATTRS = ASSETID,NAME
    -> geospatial_output (writer GENERIC_1)
    -> Junction_2
Junction

Bookmark: INPUT EXCEL FILE
Note: Excel (XLSX) - Asset Name List / Input file must contain an attribute called ASSETID or NAME (unique id that identify asset / Sheet name must be Sheet1
Sheet1 (reader XLSXR_2)
    attributes: ASSETID char(8), NAME char(5)
    -> FeatureJoiner [LEFT]

Bookmark: INPUT URL ArcGIS REST Service
Creator
    GEOMTYPE = Geometry Object
    NUM = 1
    CREATED -> FeatureReader [INITIATOR]
FeatureReader
    ARCGISFEATURES_AUTH_TYPE = None
    ARCGISFEATURES_CREATE_FEATURE_TABLES_FROM_DATA = Yes
    ARCGISFEATURES_FEATURES_PER_REQUEST = 1000
    ARCGISFEATURES_FORMAT_GUID = YES
    ARCGISFEATURES_QUERY_FEATURE_TYPES_FOR_MERGE_FILTERS = Yes
    ARCGISFEATURES_RESOLVE_DOMAINS = No
    ARCGISFEATURES_USE_SEARCH_ENVELOPE = NO
    ARCGISFEATURES_VERIFY_HTTPS = Yes
    ATTRS_TO_EXPOSE = fme_feature_type
    ATTR_ACCUM_MODE = Only Use Result
    COMBINE_GEOM = Use Result
    DATASET = $(INPUT_ArcGIS_REST_SERVICE)
    FEATURETYPES = $(ArcGIS_REST_SERVICE_FEATURETYPES_TO_READ)
    FORMAT = ARCGISFEATURES
    INTERACT = NONE
    OUTPUT_FEATURES_DISPLAY = Schema and Data Features
    <OTHER> -> AttributeExposer_3

Bookmark: Local Geospatial Output to Support Asset Mapping
Note: attribute names in the output will be the same as the ones defined in the excel feature reader / LOCAL OUTPUT
geospatial_output (writer GENERIC_1)
    attributes: Name varchar(200)

Bookmark: Geospatial Output Available in your GIS Portal
Note: Instead of download the geospatial output in your local, you can make it available in your ArcGIS Enterprise Portal using the Writer Esri ArcGIS Portal Feature Service, allowing non GIS users to verify the location of the assets they want to target
Junction_2
